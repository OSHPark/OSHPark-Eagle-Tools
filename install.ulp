// Find some useful locations
string SELF=argv[0];
string SELF_DIR=filedir(SELF);
string ULP_DIR=path_ulp[0];
string DRU_DIR=path_dru[0];
string CAM_DIR=path_cam[0];
string SCR_DIR=path_scr[0];
string LBR_DIR=path_lbr[0];
string BIN_DIR=filedir(EAGLE_PATH);
string EAGLESCR_PATH=SCR_DIR+"/eagle.scr";
string LOGFILE="oshpark_ulp_installer.log";

void copy_file(string SOURCE, string DEST){
	char DATA[];
	int SIZE=fileread(DATA,SOURCE);
	output(DEST,"wb"){
		for (int i = 0; i < SIZE; i++) {
			printf("%c", DATA[i]);
		}
	}
}

void backup_file(string SOURCE){
	//Check to make sure the file exists
	string tmp[];
	int FOUND=fileglob(tmp,SOURCE);
	if(FOUND<1)return;

	string SUFFIX;
	sprintf(SUFFIX,".bak.%d",filetime(SOURCE));
	copy_file(SOURCE,SOURCE+SUFFIX);
}

void compare_copy(string SOURCE,string DEST){
	//See if source == dest
	int SOURCE_SIZE;
	char SOURCE_DATA[];
	int DEST_SIZE;
	char DEST_DATA[];

	printf("Checking %s and %s \n",filename(SOURCE),DEST);

	//see if file exists
	string tmp[];
	int FOUND=fileglob(tmp,DEST);
	if(FOUND==0){
		printf("> Not found! Copying...\n");
		copy_file(SOURCE,DEST);
		return;
	}

	SOURCE_SIZE=fileread(SOURCE_DATA,SOURCE);
	DEST_SIZE=fileread(DEST_DATA,DEST);

	if(SOURCE_SIZE!=DEST_SIZE){
		printf("> Different sizes! Backup and copy...\n");
		backup_file(DEST);
		copy_file(SOURCE,DEST);
		return;
	}

	//files might be the same
	for(int i=0;i<SOURCE_SIZE;i++){
		if(DEST_DATA[i]!=SOURCE_DATA[i]){
			printf("> Not identical! Backup and copy...\n");
			backup_file(DEST);
			copy_file(SOURCE,DEST);
			return;
		}
	}
	printf("> Identical! Do nothing...\n");
}

void copy_dir(string SOURCE,string DEST){
	int NUM;
	string FILES[];
	NUM=fileglob(FILES,SOURCE);
	for(int i=0; i<NUM;i++){
		compare_copy(FILES[i],DEST+"/"+filename(FILES[i]));
	}
}

output(LOGFILE,"wtD") {
	// Get the script name
	printf("Script self: %s\n",SELF);
	printf("Script self dir: %s\n",SELF_DIR);
	printf("ULP Dir: %s\n",ULP_DIR);
	printf("SCR Dir: %s\n",SCR_DIR);
	printf("BIN Dir: %s\n",BIN_DIR);

	real VERSION=EAGLE_VERSION+EAGLE_RELEASE/10.0;
	printf("Found Eagle Version %f\n",VERSION);

	// Copy over new files
	copy_dir(SELF_DIR+"/ulp/",ULP_DIR);
	copy_dir(SELF_DIR+"/bin/",BIN_DIR);
	copy_dir(SELF_DIR+"/dru/",DRU_DIR);
	copy_dir(SELF_DIR+"/lbr/",LBR_DIR);

	if(VERSION>=7.2){
		copy_dir(SELF_DIR+"/cam-7.2+/",CAM_DIR);
	}
	else{
		copy_dir(SELF_DIR+"/cam/",CAM_DIR);
	}

	string MENU_STR=" '[oshpark.png]Oshpark{Upload PCB: Run oshpark-upload.ulp;}'";
	sprintf(MENU_STR,"MENU %s;\r\n",MENU_STR);

	// Dig through the existing Eagle.scr and add our menu item
	string EAGLE_SCR_DATA[];
	int EAGLE_SCR_DATA_SIZE;
	EAGLE_SCR_DATA_SIZE=fileread(EAGLE_SCR_DATA,SCR_DIR+"/eagle.scr");

	string LINE;
	int BRD_START=-1;
	int BRD_END=-1;
	int i;

	// Find the BRD section
	for(i=0;i<EAGLE_SCR_DATA_SIZE; i++){
		LINE=EAGLE_SCR_DATA[i];
		BRD_START=i;
		if(strstr(LINE,"BRD:")==0 ){
			break;
		}
	}
	// Scan for the next section
	for(i=BRD_START+1;i<EAGLE_SCR_DATA_SIZE; i++){
		LINE=EAGLE_SCR_DATA[i];
		BRD_END=i;
		if(strxstr(LINE,"[A-Z]{3}:")==0 ){
			break;
		}
	}
	printf("Found a brd section from %d to %d\n", BRD_START,BRD_END);

	//don't mangle the file unless we need to.

	if(BRD_END>0 && strstr(EAGLE_SCR_DATA[BRD_END-1],MENU_STR)>=0){
		printf("Menu already installed!\n");
		printf("> %s\n", EAGLE_SCR_DATA[BRD_END-1]);
	}
	else{
		printf("Installing menu.!\n");
		printf(">> %s",MENU_STR);

		backup_file(EAGLESCR_PATH);
		// Print a new menu line at the end of the BRD section
		output(EAGLESCR_PATH,"wt"){
			for(i=0;i<EAGLE_SCR_DATA_SIZE; i++){
				if(i==BRD_END && BRD_START==EAGLE_SCR_DATA_SIZE){
					printf("BRD:\r\n");
					}
				if(i==BRD_END){
					printf(MENU_STR);
				}
				printf("%s\r\n",EAGLE_SCR_DATA[i]);
			}
		}
	}
}
